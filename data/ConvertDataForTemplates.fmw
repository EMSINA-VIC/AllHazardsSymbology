FME workspace ConvertDataForTemplates.fmw

Parameters:
- SourceDataset_SHAPE = ""$(FME_MF_DIR)Template_Line.shp" "$(FME_MF_DIR)Template_Point.shp" "$(FME_MF_DIR)Template_Polygon.shp""   # Source Esri Shape File(s)
- DestDataset_GEOJSON = $(FME_MF_DIR)Template.json   # Destination GeoJSON File

Readers:
- SHAPE_1: SHAPE from $(SourceDataset_SHAPE)

Writers:
- GEOJSON_1: GEOJSON to $(DestDataset_GEOJSON)

Template_Line (reader SHAPE_1)
    attributes: Id number(6,0), Symbol char(50), Feature char(65), Theme char(15), AIIMS char(10), Orient number(2,0)
    -> Template_Line (writer GEOJSON_1)
Template_Line (writer GEOJSON_1)
    attributes: Id int, Symbol string, Feature string, Theme string, AIIMS string, Orient int
Template_Point (reader SHAPE_1)
    attributes: Id number(6,0), Symbol char(50), Feature char(55), Theme char(20), AIIMS char(15)
    -> Template_Point (writer GEOJSON_1)
Template_Point (writer GEOJSON_1)
    attributes: Id int, Symbol string, Feature string, Theme string, AIIMS string
Template_Polygon (reader SHAPE_1)
    attributes: Id number(6,0), Symbol char(50), Feature char(65), Theme char(15), AIIMS char(10)
    -> Template_Polygon (writer GEOJSON_1)
Template_Polygon (writer GEOJSON_1)
    attributes: Id int, Symbol string, Feature string, Theme string, AIIMS string
